string Version = "1.11";

char Separator = ';';

int ShowPart = 1;
int ShowValue = 1;
int ShowDevice = 1;
int ShowPackage = 1;
int ShowDescription = 1;
int ShowQty = 1;

string I18N[] = {
  "en\v"
  "de\v"
  ,
  "<hr><b>ERROR: No schematic!</b><p>\nThis program can only work in the schematic editor.\v"
  "<hr><b>FEHLER: Kein Schaltplan!</b><p>\nDieses Program kann nur in einem Schaltplan verwendet"
  " werden.\v"
  ,
  "Part\tValue\tDevice\tPackage\tDescription\v"
  "Bauteil\tWert\tDevice\tPackage\tDescription\v"
  ,
  "Qty\tValue\tDevice\tPackage\tParts\v"
  "Menge\tWert\tDevice\tGehäuse\tBauteile\v"
  ,
  "Partlist exported from %s at %s\v"
  "Stückliste exportiert aus %s am %s\v"
  ,
  "Bill Of Material - Preview\v"
  "Stückliste - Vorschau\v"
  ,
  "-Close\v"
  "-Schließen\v"
  ,
  "Save Bill Of Material\v"
  "Stückliste speichern\v"
  ,
  "File '\v"
  "Datei '\v"
  ,
  "' exists\n\nOverwrite?\v"
  "' existiert\n\nÜberschreiben?\v"
  ,
  "+&Yes\v"
  "+&Ja\v"
  ,
  "-&No\v"
  "-&Nein\v"
  ,
  "&No\v"
  "&Nein\v"
  ,
  "Name already defined!\v"
  "Name ist bereits definiert!\v"
  ,
  " Header\v"
  " Spaltenüberschrift\v"
  ,
  "&Name:\v"
  "&Name:\v"
  ,
  "+OK\v"
  "+OK\v"
  ,
  "Name can't be empty!\v"
  "Name kann nicht leer sein!\v"
  ,
  "-Cancel\v"
  "-Abbrechen\v"
  ,
  "&Headers\v"
  "&Spaltenüberschriften\v"
  ,
  "Bill Of Material - Help\v"
  "Stückliste - Hilfe\v"
  ,
  "Bill Of Material\v"
  "Stückliste\v"
  ,
  "Output format\v"
  "Ausgabeformat\v"
  ,
  "&Text\v"
  "&Text\v"
  ,
  "&CSV\v"
  "&CSV\v"
  ,
  "&HTML\v"
  "&HTML\v"
  ,
  "+Vie&w\v"
  "+&Vorschau\v"
  ,
  "&Save...\v"
  "&Speichern...\v"
  };
int Language = strstr (I18N [0], language ()) / 3;

string tr (string s) {
  string t = lookup (I18N, s, Language, '\v');
  return t ? t : s;
}

if (!schematic) {
  dlgMessageBox (usage + tr ("<hr><b>ERROR: No schematic!</b><p>\nThis program can only work in"
                 " the schematic editor."));
  exit (1);
}

string SeparatorString;
int     NumParts;
numeric string Lines[];
numeric string PartName[];
string  PartValue[], PartDevice[], PartPackage[], PartHeadline[];
numeric string PartDescription [];
int     PartValueOn[];
int     Selected;

int UseAttributes = 1;
int FoundAttributes = 0;
numeric string AttributesList[];
numeric string PartAttributes[];

enum { ltParts, ltValues };
enum { ofText, ofCSV, ofHTML };
int ListType = ltParts;
int OutputFormat = 0;

string StripWhiteSpace (string s) {
  while (s && isspace (s[0]))
    s = strsub (s, 1);
  while (s && isspace (s[strlen (s) - 1]))
    s = strsub (s, 0, strlen (s) - 1);
  return s;
}

string ReplaceTabs(string s) {
  int i;
  while ((i = strchr(s, '\t')) >= 0)
        s = strsub(s, 0, i) + "\\t" + strsub(s, i + 1);
  return s;
}

void CollectPartData (string var) {
  int Found = 0;
  int i;
  string attr[];

  NumParts = 0;

  FoundAttributes = 0;
  if (UseAttributes) {
    schematic (SCH) {
      SCH.allparts (P) {
        if (P.device.package) {
          if (P.populate) {
            P.attributes (A) {
              if (0 == FoundAttributes) {
                AttributesList[0] = A.name;
                FoundAttributes = 1;
              } else {
                Found = 0;
                for (i = 0; i < FoundAttributes; i ++) {
                  if (A.name == AttributesList[i]) {
                    Found = 1;
                    break;
                  }
                }
                if (0 == Found) {
                  AttributesList[FoundAttributes] = A.name;
                  FoundAttributes ++;
                }
              }
            }
          }
        }
      }
    }
    sort (FoundAttributes, AttributesList);
  }
  schematic (SCH) {
    SCH.allparts (P) {
      if (P.device.package) {
        if (P.populate) {
          PartName[NumParts] = P.name;
          PartValue[NumParts] = P.value;
          PartDevice[NumParts] = P.device.name;
          PartPackage[NumParts] = P.device.package.name;
          PartHeadline[NumParts] = ReplaceTabs(P.device.headline);
          PartValueOn[NumParts] = P.device.value == "On";
          for (i = 0; i < FoundAttributes; i ++)
            attr[i] = "";
          P.attributes(A) {
            for (i = 0; i < FoundAttributes; i ++)
              if (A.name == AttributesList[i]) {
                attr[i] = A.value;
                break;
              }
            if ("VALUE" == A.name && 0 < strlen (A.value))
            PartValueOn[NumParts] = 2;
          }
          PartAttributes[NumParts] = strjoin(attr, Separator);
          NumParts ++;
        }
      }
    }
  }
}

string GenerateHeader() {
    string header = "";
    if (ShowQty) header += "Qty";
    if (ShowValue) header += (header == "" ? "" : "\t") + "Value";
    if (ShowDevice) header += (header == "" ? "" : "\t") + "Device";
    if (ShowPackage) header += (header == "" ? "" : "\t") + "Package";
    if (ShowPart) header += (header == "" ? "" : "\t") + "Part";
    if (ShowDescription) header += (header == "" ? "" : "\t") + "Description";

    return header;
}

string UpdateLine(int index, int qty, string partsList) {
    string line = "";
    if (ShowQty) {
        string Quantity;
        sprintf(Quantity, "%d", qty);
        line += Quantity;
    }
    if (ShowValue) line += (line == "" ? "" : "\t") + PartValue[index];
    if (ShowDevice) line += (line == "" ? "" : "\t") + PartDevice[index];
    if (ShowPackage) line += (line == "" ? "" : "\t") + PartPackage[index];
    if (ShowPart) line += (line == "" ? "" : "\t") + partsList;
    if (ShowDescription) line += (line == "" ? "" : "\t") + PartHeadline[index];

    return line;
}

void GeneratePartList(void) {
    int NumLines = 0;
    Lines[NumLines++] = GenerateHeader();

    int Index[];
    sort(NumParts, Index, PartValue, PartDevice, PartPackage, PartAttributes, PartName, PartHeadline);
    for (int n1 = 0, n2 = 0; ++n2 <= NumParts;) {
        int i1 = Index[n1];
        string partsList = PartName[i1];
        if (n2 < NumParts) {
            int i2 = Index[n2];
            while (PartValue[i1] == PartValue[i2] && PartDevice[i1] == PartDevice[i2] && PartPackage[i1] == PartPackage[i2] && n2 < NumParts) {
                partsList += ", " + PartName[i2];
                if (++n2 < NumParts) {
                    i2 = Index[n2];
                }
            }
        }
        Lines[NumLines] = UpdateLine(i1, n2 - n1, partsList);
        n1 = n2;
        NumLines++;
    }
    Lines[NumLines] = "";
}

void GenerateList(void) {
    GeneratePartList();
}

string MakeListHeader (void) {
  string s;
  schematic(SCH)
    sprintf (s, tr ("Partlist exported from %s at %s"), SCH.name, t2string (time ()));
  return s;
}

string MakeListText(void) {
    int l, Width[];
    string List;
    int numHeaders;

    for (l = 0; Lines[l]; l++) {
        string a[];
        for (int n = strsplit(a, Lines[l], '\t'); n--; ) {
            Width[n] = max(Width[n], strlen(a[n]));
        }
    }

    List = MakeListHeader() + "\n\n";

    for (l = 0; Lines[l]; l++) {
        string line, a[];

        int n = strsplit(a, Lines[l], '\t');
        if (l == 0) {
            numHeaders = n;
        } else {
            n = numHeaders;
        }
        for (int i = 0; i < n; i++) {
            string s;
            sprintf(s, "%s%-*s", line ? " " : "", Width[i], a[i]);
            line += s;
        }
        List += line + "\n";
    }
    return List;
}

string MakeListCSV(void) {
    string List;
    int numHeaders;

    for (int l = 0; Lines[l]; l++) {
        string a[];
        int n = strsplit(a, Lines[l], '\t');
        if (l == 0) {
            numHeaders = n;
        } else {
            n = numHeaders;
        }
        for (int i = 0; i < n; i++) {
            List += "\"" + a[i] + "\"" + (i < n - 1 ? SeparatorString : "");
        }
        List += "\n";
    }
    return List;
}

string MakeListHTML(void) {
    string List;
    int numHeaders;

    List = "<b>" + MakeListHeader() + "</b>\n<p>\n";
    List += "<table>\n";
    for (int l = 0; Lines[l]; l++) {
        List += "<tr>";
        string a[];
        int n = strsplit(a, Lines[l], '\t');
        if (l == 0) {
            numHeaders = n;
        } else {
            n = numHeaders;
        }
        for (int i = 0; i < n; i++) {
            if (l == 0) a[i] = "<b>" + a[i] + "</b>";
            List += "<td>" + a[i] + "</td>";
        }
        List += "</tr>\n";
    }
    List += "</table>\n";
    return List;
}

string MakeList(void) {
    switch (OutputFormat) {
        case ofText: return MakeListText(); break;
        case ofCSV: return MakeListCSV(); break;
        case ofHTML: return MakeListHTML(); break;
    }
    return "";
}

void ViewList(void) {
    dlgDialog(tr("Bill Of Material - Preview")) {
        string s = MakeList();
        if (OutputFormat == ofText || OutputFormat == ofCSV)
            s = "<pre>" + s + "</pre>";
        dlgHBoxLayout dlgSpacing(400);
        dlgHBoxLayout
        {
            dlgVBoxLayout dlgSpacing(300);
            dlgTextView(s);
        }
        dlgHBoxLayout
        {
            dlgStretch(1);
            dlgPushButton(tr("-Close")) dlgReject();
        }
    };
}

void SaveList(void) {
    string FileName;
    string FileExt;

    switch (OutputFormat)
    {
        case ofText: FileExt = ".txt"; break;
        case ofHTML: FileExt = ".html"; break;
        case ofCSV:  FileExt = ".csv"; break;
    }
    schematic(SCH) FileName = filesetext(SCH.name, FileExt);
    FileName = dlgFileSave(tr("Save Bill Of Material"), FileName);
    if (FileName)
    {
        string a[];
        if (!fileglob(a, FileName) || dlgMessageBox(tr("File '") + FileName +
            tr("' exists\n\nOverwrite?"), tr("+&Yes"), tr("-&No")) == 0)
        {
            output(FileName, "wt")
            {
                printf("%s", MakeList());
            }
        }
    }
}

schematic(SCH) {
    sprintf(SeparatorString, "%c", Separator);
}

CollectPartData("");
GenerateList();

dlgDialog(tr("Bill Of Material")) {
    dlgHBoxLayout {

        dlgGroup(tr("Output format")) {
            dlgRadioButton(tr("&Text"), OutputFormat);
            dlgRadioButton(tr("&CSV"), OutputFormat);
            dlgRadioButton(tr("&HTML"), OutputFormat);
        }
        
        dlgGroup(tr("Columns")) {
            dlgCheckBox(tr("Qty"), ShowQty) GenerateList();
            dlgCheckBox(tr("Part"), ShowPart) GenerateList();
            dlgCheckBox(tr("Value"), ShowValue) GenerateList();
            dlgCheckBox(tr("Device"), ShowDevice) GenerateList();
            dlgCheckBox(tr("Package"), ShowPackage) GenerateList();
            dlgCheckBox(tr("Description"), ShowDescription) GenerateList();
        }
    }
    dlgListView("", Lines, Selected);

    dlgHBoxLayout {
        dlgPushButton(tr("+Vie&w")) ViewList();
        dlgPushButton(tr("&Save...")) SaveList();
        dlgPushButton(tr("-Close")) dlgAccept();
        dlgStretch(1);
        dlgLabel("Version " + Version);
    }
};
